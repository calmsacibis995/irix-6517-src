-- June 1998, Version 1.0.
-- Copyright (c) 1998 by Silicon Graphics Inc. 
-- All rights reserved.

-- The SGI base SMI definitions.  This module  defines 
-- the root identifiers for the various mib groups defined 
-- by various SGI departments.

-- Based on SNMPv2-SMI 


SGI-BASE-SMI DEFINITIONS ::= BEGIN


    IMPORTS
        MODULE-IDENTITY, OBJECT-TYPE, 
	OBJECT-IDENTITY, enterprises
                FROM SNMPv2-SMI;


    sgi MODULE-IDENTITY
        LAST-UPDATED "9803312057Z"
        ORGANIZATION "Silicon Graphics Inc."
        CONTACT-INFO
	    " World Wide Web Support URL : 
		http://www.sgi.com/support/support_help.html
	      
	      North American Technical Support 
	      telephone number : 1-800-800-4SGI

	      World Wide Technical Support 
	      email-id : support@sgi.com"

	DESCRIPTION
	    " The base SMI file for the Silicon Graphics 
	    Enterprise MIB definitions.  Other MIB modules 
	    defined by SGI will be rooted from OIDs defined 
	    in this module"
	REVISION "9803312057Z"
	DESCRIPTION
	    " The initial (test) version of this MIB module"
    ::= {enterprises 59}


-- The root object identifier under which the 
-- sysObjectID for various SGI products will be 
-- defined.  Every product developed by SGI, software 
-- or hardware, will have a unique sysObjectID defined 
-- for itself much like a "Product ID". 

-- For example, indy systems will report sysObjectID as 
-- enterprises.sgi.sgiProducts.sgiWorkstations.indy

    sgiProducts OBJECT-IDENTITY
	STATUS current
 	DESCRIPTION
	    "The authoritative root identifier under 
	    which the sysObjectID for all SGI products 
	    will be defined.  Actual definitions will
	    be defined in a separate MIB module."
    ::= {sgi 1}



-- Independent groups across the organization may 
-- develop applications which may support their own 
-- MIB objects.  These applications may run on various 
-- Operating Systems and shouldn't be tied to a particular
-- OS-based subtree.

-- This oid is defined so that the mibs of various 
-- applications can be rooted under this.  

-- For example, multiUserServer ::= {sgiApplications 1}
-- 		gauntlet ::= {sgiApplications 2}

    sgiApplications OBJECT-IDENTITY
	STATUS current
	DESCRIPTION
	    "The authoritative root identifier under 
	    which the mib groups defined by various 
	    SGI applications will be defined."
    ::= {sgi 2}
	


-- Right now we assume that the mib objects defined 
-- with respect to the IRIX Operating System and the 
-- associated hardware will be inappropriate
-- for Windows-based systems, and the vice versa

-- But still, we have tried to define objects based 
-- on their functionality. So, we may have to make 
-- some changes when it comes to define objects for
-- windows based systems


    sgiHost OBJECT-IDENTITY
	STATUS current
	DESCRIPTION
	    "The authoritative root identifier under
	     which the mib groups representing information 
	    of a SGI host will be defined."
    ::= {sgi 3}


    sgiAgents  OBJECT-IDENTITY
	STATUS  current
	DESCRIPTION
	    " The root identifier under which 
	    information specific to various agent 
	    implementations such as AGENT CAPABILITIES
	    will be provided."
    ::= {sgi 4}

-- Any common stuff that needs to get added will go in here
	
END
