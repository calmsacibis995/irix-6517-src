-- June 1998, Version 1.0.
-- Copyright (c) 1998 by Silicon Graphics Inc. 
-- All rights reserved.

-- The SGI products MIB.  This MIB defines the "Product ID" for all SGI
-- products, software or hardware.  The product id is supposed to be 
-- unique.  
-- For hardware systems, this product id maps directly to the sysObjectID
-- defined in MIB-II (rfc1213).

-- Based on SNMPv2


SGI-PRODUCTS-SMI DEFINITIONS ::= BEGIN


    IMPORTS
        MODULE-IDENTITY, OBJECT-TYPE
                FROM SNMPv2-SMI
	sgi
		FROM SGI-BASE-SMI;


    sgiProducts MODULE-IDENTITY
        LAST-UPDATED "9806291840Z"  -- June 29 1998, 18:40 GMT
        ORGANIZATION "Silicon Graphics Inc."
        CONTACT-INFO
	    " World Wide Web Support URL : 
		http://www.sgi.com/support/support_help.html
	      
	      North American Technical Support 
	      telephone number : 1-800-800-4SGI

	      World Wide Technical Support 
	      email-id : support@sgi.com"

	DESCRIPTION
	    "The SGI Products MIB module, which contains 
	     Product ID definitions for all SGI products." 
	REVISION "9806291840Z"
	DESCRIPTION
	    " The initial (test) version of this MIB module"
    ::= {sgi 1}


-- The product id information for all the workstations 
-- from SGI

-- The root identifier for this subclass

    sgiUnknownSystem OBJECT-IDENTITY 
	STATUS current
	DESCRIPTION 
	    "The sysObjectID value for an 
	     unknown SGI system."
    ::= {sgiProducts 1}

    sgiWorkstations OBJECT-IDENTITY
	STATUS current
	DESCRIPTION
	    "The OID under which the product id for 
	     SGI workstations will be defined."
    ::= {sgiProducts 2}


-- Indigo 
    indigo OBJECT IDENTIFIER ::= {sgiWorkstations 1}

-- Indigo2 series
    indigo2      OBJECT IDENTIFIER ::= {sgiWorkstations 2}
    powerIndigo2 OBJECT IDENTIFIER ::= {sgiWorkstations 3}

-- Indy
    indy   OBJECT IDENTIFIER ::= {sgiWorkstations 4}

-- O2
    o2     OBJECT IDENTIFIER ::= {sgiWorkstations 5}

-- Octane
    octane OBJECT IDENTIFIER ::= {sgiWorkstations 6}

--Onyx2
    onyx       OBJECT IDENTIFIER ::= {sgiWorkstations 7}
    onyx2      OBJECT IDENTIFIER ::= {sgiWorkstations 8}
    powerOnyx2 OBJECT IDENTIFIER ::= {sgiWorkstations 9}

-- servers root

    sgiServers OBJECT-IDENTITY
	STATUS current
	DESCRIPTION
	    "The OID under which the product id for 
	     SGI Servers will be defined."
    ::= {sgiProducts 3}


-- origin200
    origin200   OBJECT IDENTIFIER ::= {sgiServers 1}

-- origin2000
    origin2000  OBJECT IDENTIFIER ::= {sgiServers 2}

-- Challenge Series
    challenge   OBJECT IDENTIFIER ::= {sgiServers 3}
    challengeDM OBJECT IDENTIFIER ::= {sgiServers 4}
    challengeL  OBJECT IDENTIFIER ::= {sgiServers 5}
    challengeM  OBJECT IDENTIFIER ::= {sgiServers 6}
    challengeXL OBJECT IDENTIFIER ::= {sgiServers 7}
    challengeS  OBJECT IDENTIFIER ::= {sgiServers 8}

    powerChallenge  OBJECT IDENTIFIER ::= {sgiServers 9}
    powerChallengeM OBJECT IDENTIFIER ::= {sgiServers 10}

-- Supercomputers root

    sgiSupercomputers OBJECT-IDENTITY
	STATUS current
	DESCRIPTION
	    "The OID under which the product id for 
	     SGI Supercomputers will be defined."
    ::= {sgiProducts 4}


-- CRAY Origin2000
    crayOrigin2000 OBJECT IDENTIFIER ::= {sgiSupercomputers 1}

-- CRAY T90 series
    crayT94        OBJECT IDENTIFIER ::= {sgiSupercomputers 2}
    crayT916       OBJECT IDENTIFIER ::= {sgiSupercomputers 3}
    crayT932       OBJECT IDENTIFIER ::= {sgiSupercomputers 4}

-- CRAY J90 series
    crayJ916       OBJECT IDENTIFIER ::= {sgiSupercomputers 5}
    crayJ932       OBJECT IDENTIFIER ::= {sgiSupercomputers 6}
    crayJ90se      OBJECT IDENTIFIER ::= {sgiSupercomputers 7}

-- CRAY T3E series
    crayT3E        OBJECT IDENTIFIER ::= {sgiSupercomputers 8}
    crayT3E-900    OBJECT IDENTIFIER ::= {sgiSupercomputers 9}
    crayT3E-1200   OBJECT IDENTIFIER ::= {sgiSupercomputers 10}


-- A LOT more definitions will probably need to go in here

END
