SGI-MIB DEFINITIONS ::= BEGIN

IMPORTS
    MODULE-IDENTITY, OBJECT-TYPE, Integer32
        FROM SNMPv2-SMI
    TEXTUAL-CONVENTION, DisplayString
        FROM SNMPv2-TC
    MODULE-COMPLIANCE, OBJECT-GROUP
        FROM SNMPv2-CONF;

sgi	OBJECT IDENTIFIER ::= { enterprises 59 }

sgiMIB MODULE-IDENTITY
    LAST-UPDATED "9701290000Z"
    ORGANIZATION "Silicon Graphics, Inc."
    CONTACT-INFO
            "        Network Management Group

             Postal: Silicon Graphics, Inc.
                     2011 N. Shoreline Blvd
                     Mountain View, CA 94043
                     USA

                Tel: +1 415 933 4000

             E-mail: n/a"
    DESCRIPTION
            "The MIB module for documenting SGI's private MIB."
    ::= { sgi 5 }



sgiSystem	OBJECT IDENTIFIER ::= { sgi 3 }

sgiProcessor	OBJECT IDENTIFIER ::= { sgiSystem 1 }

sgiProcTable OBJECT-TYPE
	SYNTAX SEQUENCE OF SgiProcEntry
	MAX-ACCESS not-accessible
	STATUS current
	DESCRIPTION
	"The system processor table describes the types of processors
	available in the SGI host."
	::= { sgiProcessor 1 }

sgiProcEntry OBJECT-TYPE
	SYNTAX  SgiProcEntry
	MAX-ACCESS not-accessible
	STATUS  current
	DESCRIPTION
	"A row of the system processor table."
	INDEX	{ sgiProcIndex }
	::= { sgiProcTable 1 }

SgiProcEntry ::= SEQUENCE {
	sgiProcIndex 		Integer32,
	sgiProcType 		Integer32,
	sgiProcFrequency 	Integer32,
	sgiProcCpuType 		Integer32,
	sgiProcCpuMajorRev 	Integer32,
	sgiProcCpuMinorRev 	Integer32,
	sgiProcFpuType 		Integer32,
	sgiProcFpuMajorRev 	Integer32,
	sgiProcFpuMinorRev 	Integer32,
	sgiProcEnabled 		Integer32,
	sgiProcMaster 		Integer32,
	sgiProcClock 		Integer32,
	sgiProcFastClock 	Integer32,
	sgiProcIsolated 	Integer32,
	sgiProcBroadcast 	Integer32,
	sgiProcPreemptive 	Integer32
}

sgiProcIndex OBJECT-TYPE
	SYNTAX  Integer32
	MAX-ACCESS not-accessible 
	STATUS  current
	DESCRIPTION
	"The index into the system processor table."
	::= { sgiProcEntry 1 }

sgiProcType OBJECT-TYPE
	SYNTAX  Integer32
	MAX-ACCESS  read-only
	STATUS  current
	DESCRIPTION
	"The type of processor as specified in the list below.
	Note also that the MIB-II sysObjectID is derived from this
	processor type, by following the convention:
		.1.3.6.1.4.1.59.1.sgiProcType

	1       Unknown System Type

	10      Iris 1200
	11      Iris 2400
	12      Iris 2500
	13      Iris 3010
	14      Iris 3020
	15      Iris 3030
	16      Iris 3110
	17      Iris 3115
	18      Iris 3120
	19      Iris 3130

	20      Iris 4D50
	21      Iris 4D60
	22      Iris 4D70
	23      Iris 4D80
	24      Iris 4D85

	30      Iris 4D100s
	32      Iris 4D120
	34      Iris 4D140

	40      Iris 4D200s
	41      Iris 4D210
	42      Iris 4D220
	44      Iris 4D240
	46      Iris 4D260
	48      Iris 4D280

	50      Iris 4D300s
	51      Iris 4D310
	52      Iris 4D320
	54      Iris 4D340
	56      Iris 4D360
	58      Iris 4D380

	60      Iris 4D400s
	62      Iris 4D420
	64      Iris 4D440
	66      Iris 4D460
	68      Iris 4D480

	70      Crimsons
	71      Crimson

	100     Iris 4D20
	101     Iris 4D25
	110     Iris 4D30
	111     Iris 4D35

	112     Indigo
	113     Indigo R4000

	120     Indigo2
	121     Indigo2 R8000
	122     Indigo2 R10000

	130     Indy
	140     O2

	15x     Octane (x denotes the number of processors 1-2)
	16x     Origin 200 (x denotes the number of processors 1-4)
	10xx    Challenge (x denotes the number of processors 1-36)
	15xx    Power Challenge (x denotes the number of processors 1-24)
	2xxx    Origin 2000 (x denotes the number of processors 1-128)"
	::= { sgiProcEntry 2 }

sgiProcFrequency OBJECT-TYPE
	SYNTAX  Integer32
	MAX-ACCESS  read-only
	STATUS  current
	DESCRIPTION
	"The processor clock speed."
	::= { sgiProcEntry 3 }

sgiProcCpuType OBJECT-TYPE
	SYNTAX  Integer32
	MAX-ACCESS  read-only
	STATUS  current
	DESCRIPTION
	"The type of CPU."
	::= { sgiProcEntry 4 }

sgiProcCpuMajorRev OBJECT-TYPE
	SYNTAX  Integer32
	MAX-ACCESS  read-only
	STATUS  current
	DESCRIPTION
	"Co-processor major revision number."
	::= { sgiProcEntry 5 }

sgiProcCpuMinorRev OBJECT-TYPE
	SYNTAX  Integer32
	MAX-ACCESS  read-only
	STATUS  current
	DESCRIPTION
	"Co-processor minor revision number."
	::= { sgiProcEntry 6 }
                          
sgiProcFpuType OBJECT-TYPE
	SYNTAX  Integer32
	MAX-ACCESS  read-only
	STATUS  current
	DESCRIPTION
	"Type of floating-point processing unit."
	::= { sgiProcEntry 7 }
                          
sgiProcFpuMajorRev OBJECT-TYPE
	SYNTAX  Integer32
	MAX-ACCESS  read-only
	STATUS  current
	DESCRIPTION
	"Floating-point processing unit major revision number."
	::= { sgiProcEntry 8 }
                          
sgiProcFpuMinorRev OBJECT-TYPE
	SYNTAX  Integer32
	MAX-ACCESS  read-only
	STATUS  current
	DESCRIPTION
	"Floating-point processing unit minor revision number."
	::= { sgiProcEntry 9 }
                         	 
sgiProcEnabled OBJECT-TYPE
	SYNTAX  Integer32
	MAX-ACCESS  read-only
	STATUS  current
	DESCRIPTION
	"
	"
	::= { sgiProcEntry 10 }
                          
sgiProcMaster OBJECT-TYPE
	SYNTAX  Integer32
	MAX-ACCESS  read-only
	STATUS  current
	DESCRIPTION
	"
	"
	::= { sgiProcEntry 11 }
                          
sgiProcClock OBJECT-TYPE
	SYNTAX  Integer32
	MAX-ACCESS  read-only
	STATUS  current
	DESCRIPTION
	"
	"
	::= { sgiProcEntry 12 }
                          
sgiProcFastClock OBJECT-TYPE
	SYNTAX  Integer32
	MAX-ACCESS  read-only
	STATUS  current
	DESCRIPTION
	"
	"
	::= { sgiProcEntry 13 }
	
sgiProcIsolated OBJECT-TYPE
	SYNTAX  Integer32
	MAX-ACCESS  read-only
	STATUS  current
	DESCRIPTION
	"
	"
	::= { sgiProcEntry 14 }

sgiProcBroadcast OBJECT-TYPE
	SYNTAX  Integer32
	MAX-ACCESS  read-only
	STATUS  current
	DESCRIPTION
	"
	"
	::= { sgiProcEntry 15 }

sgiProcPreemptive OBJECT-TYPE
	SYNTAX  Integer32
	MAX-ACCESS  read-only
	STATUS  current
	DESCRIPTION
	"
	"
	::= { sgiProcEntry 16 }

-- The SGI graphics processor group

sgiGraphicsTable OBJECT-TYPE
	SYNTAX  SEQUENCE OF SgiGraphicsEntry
	MAX-ACCESS not-accessible
	STATUS current
	DESCRIPTION
	"
	"
	::= { sgiProcessor 2 }

sgiGraphicsEntry OBJECT-TYPE
	SYNTAX  SgiGraphicsEntry
	MAX-ACCESS not-accessible
	STATUS current
	DESCRIPTION
	"
	"
	INDEX	{ sgiGraphicsIndex }
	::= { sgiGraphicsTable 1 }

SgiGraphicsEntry ::= SEQUENCE {
	sgiGraphicsIndex 	Integer32,
	sgiGraphicsType 	Integer32,
	sgiGraphicsQual 	Integer32
}

sgiGraphicsIndex OBJECT-TYPE
	SYNTAX  Integer32
	MAX-ACCESS not-accessible
	STATUS  current
	DESCRIPTION
	"
	"
	::= { sgiGraphicsEntry 1 }

sgiGraphicsType OBJECT-TYPE
	SYNTAX  Integer32
	MAX-ACCESS  read-only
	STATUS  current
	DESCRIPTION
	"
	"
	::= { sgiGraphicsEntry 2 }

sgiGraphicsQual OBJECT-TYPE
	SYNTAX  Integer32
	MAX-ACCESS  read-only
	STATUS  current
	DESCRIPTION
	"
	"
	::= { sgiGraphicsEntry 3 }

-- SGI NetVisualizer group

sgiNv OBJECT IDENTIFIER ::= { sgi 4 }

sgiNvStationType OBJECT-TYPE
	SYNTAX  Integer32
	MAX-ACCESS  read-only
	STATUS  current
	DESCRIPTION
	"
	"
	::= { sgiNv 1 }

END
